ReportsConnections DEFINITIONS IMPLICIT TAGS ::=
BEGIN

EXPORTS ConnectionsReport, CallsRecords;

IMPORTS  DateAndTime
    FROM Sorm

	 Location
    FROM Locations

	 ReportedIdentifier
    FROM ReportedIdentifiers

	 Bunch,
	 NetworkPeerInfo,
	 DataNetworkEquipment,
	 DataVoipNumber,
	 IPAddress,
	 VoipProtocol,
	 IMProtocol,
	 HttpMethod
    FROM NetworkIdentifiers

	 PhoneAbonentType,
	 TelcoID
    FROM Dictionaries

	 TAGGED,
	 sorm-report-connection-pager,
	 sorm-report-connection-pstn,
	 sorm-report-connection-mobile,
	 sorm-report-connection-ipdr-header,
	 sorm-report-connection-aaa-login,
	 sorm-report-connection-resource,
	 sorm-report-connection-email,
	 sorm-report-connection-im,
	 sorm-report-connection-voip,
	 sorm-report-connection-file-transfer,
	 sorm-report-connection-term-access,
	 sorm-report-connection-raw-flows,
	 sorm-report-connection-address-translations
    FROM Classification;


ConnectionsReport ::= CallsRecords


CallsRecords ::= SEQUENCE {
  id TAGGED.&id ({ReportedCallsVariants}),
  data TAGGED.&Data ({ReportedCallsVariants}{@id})
}

ReportedCallsVariants TAGGED ::= {
    pagerRecord
  | pstnRecord
  | mobileRecord
  | dataAAARecord
  | dataEmailRecord
  | dataImRecord
  | dataFileTransferRecord
  | dataTermAccessRecord
  | dataRawFlowsRecord
  | dataResourceRecord
  | dataVoipRecord
  | dataAddressTranslationRecord
}


-- Детализированные записи отправки пэйджинг-сообщений
pagerRecord TAGGED ::= {
   OID { sorm-report-connection-pager }
   DATA SEQUENCE OF PagerRecordContent
}

PagerRecordContent ::= SEQUENCE {
  telco-id           TelcoID,							--- идентификатор оператора связи или филиала
  call-type-id       INTEGER  (0 .. 4294967295),				--- тип соединения
  connection-time    DateAndTime,						--- дата и время передачи сообщения
  info               ReportedIdentifier,					--- идентификаторы абонента
  in-bytes-count     INTEGER (0 .. 1024),					--- объем переданных данных
  term-cause         INTEGER (0 .. 16384)					--- причина завершения соединения
}

-- Детализированные записи звонков абонентов ТФОП, в т.ч. и неудавшиеся попытки соединений
pstnRecord TAGGED ::= {
  OID { sorm-report-connection-pstn }
  DATA SEQUENCE OF PstnRecordContent
}

PstnRecordContent ::= SEQUENCE {
  telco-id                  TelcoID,						--- идентификатор оператора связи или филиала
  begin-connection-time     DateAndTime,					--- дата и время начала соединения
  duration                  INTEGER (0 .. 86399),				--- время соединения
  call-type-id              INTEGER  (0 .. 4294967295),				--- тип соединения
  supplement-service-id     INTEGER (0 .. 4294967295),				--- ДВО при соединении
  in-abonent-type           PhoneAbonentType,					--- тип вызывающего абонента
  out-abonent-type          PhoneAbonentType,					--- тип вызываемого абонента
  switch-id		    UTF8String (SIZE (1 .. 128)),			--- код коммутатора обслужившего соединение
  inbound-bunch             INTEGER (0 .. 4294967295),				--- входящий пучок
  outbound-bunch            INTEGER (0 .. 4294967295),				--- исходящий пучок
  term-cause                INTEGER (0 .. 16384),				--- причина завершения соединения

  phone-card-number [0]     NumericString (SIZE (1.. 20)) OPTIONAL,		--- номер телефонной карты
  in-info [1]               ReportedIdentifier OPTIONAL,			--- идентификаторы вызывающего абонента
  dialed-digits [2]         UTF8String (SIZE (2 .. 32)),			--- набранный номер вызываемого абонента
  out-info [3]              ReportedIdentifier OPTIONAL,			--- идентификаторы вызываемого абонента
  forwarding-identifier [4] UTF8String (SIZE (2 .. 32)) OPTIONAL,		--- телефонный номер при переадресации
  border-switch-id [5]      UTF8String (SIZE (1 .. 128)) OPTIONAL		--- код пограничного коммутатора
}

-- Детализированные записи звонков мобильных абонентов, в т.ч. и неудавшиеся попытки соединений
-- Должны содержать также записи об SMS, в т.ч. и неудавшиеся попытки отправки
mobileRecord TAGGED ::= {
  OID { sorm-report-connection-mobile }
  DATA SEQUENCE OF MobileRecordContent
}

MobileRecordContent ::= SEQUENCE {
  telco-id                  TelcoID,						--- идентификатор оператора связи или филиала
  begin-connection-time     DateAndTime,					--- дата и время начала соединения
  duration                  INTEGER (0 .. 86399),				--- время соединения
  call-type-id              INTEGER (0 .. 4294967295),				--- тип соединения
  supplement-service-id     INTEGER (0 .. 4294967295),				--- ДВО при соединении
  in-abonent-type           PhoneAbonentType,					--- тип вызывающего абонента
  out-abonent-type          PhoneAbonentType,					--- тип вызываемого абонента
  switch-id                 UTF8String (SIZE (1 .. 128)),			--- код коммутатора обслужившего соединении
  term-cause                INTEGER (0 .. 16384),				--- причина завершения соединения

  inbound-bunch [0]         Bunch OPTIONAL,					--- входящий пучок
  outbound-bunch [1]        Bunch OPTIONAL,					--- исходящий пучок
  in-info [2]               ReportedIdentifier OPTIONAL,			--- идентификаторы вызывающего абонента
  in-end-location [3]       Location OPTIONAL,					--- местоположение вызывающего абонента на конец вызова
  in-begin-location [4]     Location OPTIONAL,					--- местоположение вызывающего абонента на начало вызова
  out-info [5]              ReportedIdentifier OPTIONAL,			--- идентификаторы вызываемого абонента
  out-begin-location [6]    Location OPTIONAL,					--- местоположение вызываемого абонента на начало вызова
  out-end-location [7]      Location OPTIONAL,					--- местоположение вызываемого абонента на конец вызова
  forwarding-identifier [8] UTF8String (SIZE (2 .. 32)) OPTIONAL,		--- телефонный номер при переадресации
  roaming-partner-id [9]    INTEGER (0 .. 4294967295) OPTIONAL,		        --- код роумингового партнера
  border-switch-id [10]     UTF8String (SIZE (1 .. 128)) OPTIONAL		--- код пограничного коммутатора
}

--- запись IPDR подключения/отключения абонента к сети связи
dataAAARecord TAGGED ::= {
  OID { sorm-report-connection-aaa-login }
  DATA SEQUENCE OF DataAAARecordContent
}

DataAAARecordContent ::= SEQUENCE {
  telco-id                  TelcoID,						--- идентификатор оператора связи или филиала
  point-id                  INTEGER (0 .. 1000),				--- идентификатор точки подключения к сети передачи данных, с которой получена запись о соединении
  aaa-connection-time       DateAndTime,					--- дата и время подключения/отключения к сети передачи данных
  aaa-login-type ENUMERATED {							--- тип соединения
      connect (0),								--- подключение к сети передачи данных
      disconnect (1)								--- отключение от сети передачи данных
  },
  aaa-session-id            UTF8String (SIZE (1 .. 64)),			--- идентификатор сессии
  aaa-allocated-ip          IPAddress,						--- выделенный динамический IP-адрес
  aaa-user-name             UTF8String (SIZE (1 .. 64)),			--- имя пользователя (логин)
  aaa-connect-type          INTEGER (0 .. 65535),				--- код протокола в соответствии с RFC1700 либо номер порта для TCP/UDP
  aaa-calling-number        UTF8String (SIZE (2 .. 18)),			--- вызывающий номер
  aaa-called-number         UTF8String (SIZE (2 .. 18)),			--- вызываемый номер
  aaa-nas                   NetworkPeerInfo,					--- IP-адрес/порт NAS-сервера
  aaa-in-bytes-count        INTEGER (0 .. 18446744073709551615),		--- объем принятых данных
  aaa-out-bytes-count       INTEGER (0 .. 18446744073709551615),		--- объем переданных данных
  aaa-user-password [0]     UTF8String (SIZE (1 .. 16)) OPTIONAL,		--- пользовательский пароль
  aaa-user-equipment [1]    DataNetworkEquipment OPTIONAL,			--- идентификатор пользовательского оборудования
  aaa-apn [2]     	    UTF8String (SIZE (1 .. 32)) OPTIONAL,		--- наименование точки доступа (Access Point Name)
  aaa-sgsn-ip [3]	    IPAddress OPTIONAL,					--- IP-адрес GPRS/EDGE SGSN
  aaa-ggsn-ip	[4]	    IPAddress OPTIONAL,					--- IP-адрес GPRS/EDGE GGSN
  aaa-service-area-code	[5] INTEGER (0 .. 65535) OPTIONAL,			--- код зоны обслуживания (SAC) GPRS/EDGE
  aaa-location-start [6]    Location OPTIONAL,					--- базовая станция, через которую установлено соединение (передача данных посредством подвижной сети связи)
  aaa-location-end [7]      Location OPTIONAL,					--- базовая станция, через которую завершено соединение (передача данных посредством подвижной сети связи)
  phone-card-number [8]     NumericString (SIZE (20)) OPTIONAL,			--- номер телефонной карты
  aaa-imsi  [9]             NumericString  (SIZE (10 .. 18)) OPTIONAL,		--- IMSI мобильного абонента
  aaa-imei [10]             NumericString (SIZE (10 .. 18)) OPTIONAL,		--- идентификатор мобильной станции абонента
  aaa-esn [11]              NumericString (SIZE (10 .. 18)) OPTIONAL,		--- идентификатор мобильной станции абонента
  aaa-pool-number [12]      UTF8String(SIZE (2 .. 18)) OPTIONAL			--- номер модемного пула
}


--- запись IPDR передачи почтового сообщения
dataEmailRecord TAGGED ::= {
  OID { sorm-report-connection-email }
  DATA SEQUENCE OF DataEmailRecordContent
}

DataEmailRecordContent ::= CHOICE {
  mail-aaa [0]  DataEmailRecordContentAAA,
  mail-ipdr [1] DataEmailRecordContentIPDR
}

DataEmailRecordContentIPDR ::= SEQUENCE {
  mail-cdr-header DataNetworkCdrHeader,						--- заголовок IPDR-соединения
  mail-event      EmailEvent,							--- тип события
  mail-sender     UTF8String (SIZE (1 .. 256)),					--- отправитель почтового сообщения
  mail-receiver   EmailReceivers,					        --- получатель почтового сообщения
  mail-cc         EmailReceivers,					        --- получатель-копия почтового сообщения
  mail-subject    UTF8String (SIZE (1 .. 256)),					--- тема почтового сообщения
  mail-size       INTEGER (0 .. 4294967295),					--- размер почтового сообщения, включая прикрепленные файлы, байт
  attachements    INTEGER (0 ..1),						--- наличие прикрепленных файлов в письме (да/нет)
  mail-servers    EmailServers,				 			--- список текстовых наименований почтовых серверов, через которые отправлено письмо (в т.ч. сервера веб-почты)
  mail-term-cause INTEGER (0 .. 16384),						--- причина завершения соединения

  mail-reply-to   UTF8String (SIZE (1 .. 256)) OPTIONAL,			--- имя и адрес, куда следует адресовать ответы на письмо
  mail-protocol   ENUMERATED {					        	--- протокол, при помощи которого отправлено сообщение
      smtp(0),
      pop3(1),
      imap(2),
      web-mail(3)
  } OPTIONAL,
  mail-abonent-id [0] UTF8String (SIZE (0 .. 64)) OPTIONAL	       	       	--- идентификатор абонента
}

DataEmailRecordContentAAA ::= SEQUENCE {
  mail-cdr-header DataNetworkCdrHeader,						--- заголовок IPDR-соединения
  mail-event      EmailEvent,							--- тип события
  mail-aaa-info   IP-AAAInformation 						--- пользовательские реквизиты входа
}

EmailEvent ::= ENUMERATED
{
	email-send(1),
	email-receive(2),
	email-download(3),
	email-logon-attempt(4),
	email-logon(5),
	email-logon-failure(6),
	email-logoff(7),
	email-partial-download(8)
}

EmailReceivers ::= SEQUENCE {
  data SEQUENCE OF UTF8String (SIZE (1 .. 256))
}

EmailServers ::= SEQUENCE {
  data SEQUENCE OF UTF8String (SIZE (1 .. 256))
}

--- запись IPDR передачи мгновенных электронных сообщений между пользователями
dataImRecord TAGGED ::= {
  OID { sorm-report-connection-im }
  DATA SEQUENCE OF DataImRecordContent
}

DataImRecordContent ::= SEQUENCE {
  im-cdr-header           DataNetworkCdrHeader,					--- заголовок IPDR-соединения
  im-user-login           UTF8String (SIZE (1 .. 20)),				--- учетная запись пользователя при подключении
  im-user-password        UTF8String (SIZE (1 .. 16)),				--- пользовательский пароль при подключении
  im-sender-screen-name   UTF8String (SIZE (1 .. 32)),				--- общедоступное имя отправителя
  im-sender-uin           UTF8String (SIZE (1 .. 256)),				--- пользовательский идентификатор отправителя (в т.ч. для веб-чата)
  im-receivers 		  ImReceivers,                                          --- список получателей сообщения
  im-size                 INTEGER (0 .. 4294967295),				--- размер данных сессии, байт
  im-term-cause           INTEGER (0 .. 16384),					--- причина завершения соединения

  im-protocol [0]         IMProtocol OPTIONAL,
  im-abonent-id [1]       UTF8String (SIZE (0 .. 64)) OPTIONAL	       	       	--- идентификатор абонента
}

ImReceivers ::= SEQUENCE OF ImReceiver

ImReceiver ::= SEQUENCE {
  im-receiver-screen-name UTF8String (SIZE (1 .. 32)),				--- общедоступное имя получателя
  im-receiver-uin         UTF8String (SIZE (1 .. 256))				--- пользовательский идентификатор получателя (в т.ч. для веб-чата)
}

--- запись IPDR передачи файловых данных
dataFileTransferRecord TAGGED ::= {
  OID { sorm-report-connection-file-transfer }
  DATA SEQUENCE OF DataFileTransferRecordContent
}

DataFileTransferRecordContent ::= SEQUENCE {
  file-cdr-header         DataNetworkCdrHeader,					--- заголовок IPDR-соединения
  file-server-name        UTF8String (SIZE (1 .. 256)),				--- название сервера
  file-user-name          UTF8String (SIZE (1 .. 64)),				--- имя пользователя, наименование учетной записи
  file-user-password      UTF8String (SIZE (1 .. 256)),				--- пользовательский пароль
  file-server-type        BOOLEAN,						--- режим работы файлового сервера (ACTIVE/PASSIVE)
  file-in-bytes-count     INTEGER (0 .. 18446744073709551615),			--- объем переданных данных (включает как соединения управления так и передачи данных), байт
  file-out-bytes-count    INTEGER (0 .. 18446744073709551615),			--- объем принятых данных (включает как соединения управления так и передачи данных), байт
  file-term-cause         INTEGER (0 .. 16384),					--- причина завершения соединения
  file-abonent-id [0]     UTF8String (SIZE (0 .. 64)) OPTIONAL	       	       	--- идентификатор абонента
}

--- запись IPDR терминального доступа к оборудованию
dataTermAccessRecord TAGGED ::= {
  OID { sorm-report-connection-term-access }
  DATA SEQUENCE OF DataTermAccessRecordContent
}

DataTermAccessRecordContent ::= SEQUENCE {
  term-cdr-header         DataNetworkCdrHeader,					--- заголовок IPDR-соединения
  term-in-bytes-count     INTEGER (0 .. 18446744073709551615),			--- объем переданных данных (включает как соединения управления так и передачи данных), байт
  term-out-bytes-count    INTEGER (0 .. 18446744073709551615),			--- объем принятых данных (включает как соединения управления так и передачи данных), байт
  term-protocol ENUMERATED {				         		--- протокол удаленного доступа к оборудованию
        telnet(0),
	ssh(1),
	scp(2)
  } OPTIONAL,
  term-abonent-id [0]     UTF8String (SIZE (0 .. 64)) OPTIONAL	       	       	--- идентификатор абонента
}

--- запись IPDR прочих данных, принимаемых, получаемых пользователем при помощи закрытых протоколов обмена
dataRawFlowsRecord TAGGED ::= {
  OID { sorm-report-connection-raw-flows }
  DATA SEQUENCE OF DataRawFlowsRecordContent
}

DataRawFlowsRecordContent ::= SEQUENCE {
  flow-cdr-header         DataNetworkCdrHeader,					--- заголовок IPDR-соединения
  flow-in-bytes-count     INTEGER (0 .. 18446744073709551615),			--- объем переданных данных (включает как соединения управления так и передачи данных), байт
  flow-out-bytes-count    INTEGER (0 .. 18446744073709551615),			--- объем принятых данных (включает как соединения управления так и передачи данных), байт
  flow-protocol ENUMERATED {			         			--- протокол передачи данных
      ip(0),
      udp(1),
      tcp(2)
  } OPTIONAL,
  flow-abonent-id [0]     UTF8String (SIZE (0 .. 64)) OPTIONAL	       	       	--- идентификатор абонента
}

--- запись IPDR HTTP-обращения к информационному ресурсу сети связи (сайт, портал)
dataResourceRecord TAGGED ::= {
  OID { sorm-report-connection-resource }
  DATA SEQUENCE OF DataResourceRecordContent
}

DataResourceRecordContent ::= SEQUENCE {
  res-cdr-header         DataNetworkCdrHeader,					--- заголовок IPDR-соединения
  res-url                UTF8String (SIZE (1 .. 1024)),				--- Наименование информационного ресурса
  res-bytes-count        INTEGER (0 .. 18446744073709551615),			--- объем принятых и переданных данных в соединении (включает как соединения управления так и передачи данных), байт
  res-term-cause         INTEGER (0 .. 16384),					--- причина завершения соединения
  res-aaa-info [0]       IP-AAAInformation OPTIONAL,				--- пользовательские реквизиты входа в информационный ресурс
  res-http-method [1]    HttpMethod OPTIONAL,				       	--- http метод
  res-abonent-id [2]     UTF8String (SIZE (0 .. 64)) OPTIONAL		       	--- идентификатор абонента
}

--- запись IPDR голосовой связи посредством сети передачи данных
dataVoipRecord TAGGED ::= {
  OID { sorm-report-connection-voip }
  DATA SEQUENCE OF DataVoipRecordContent
}

DataVoipRecordContent ::= SEQUENCE {
  voip-cdr-header      DataNetworkCdrHeader,					--- заголовок CDR-соединения
  voip-session-id      UTF8String (SIZE (1..64)),				--- идентификатор сессии/call-id
  voip-conference-id   UTF8String (SIZE (1..64)),				--- идентификатор конференции
  voip-duration        INTEGER (0 .. 86399),					--- длительность разговора, сек.
  voip-originator-name UTF8String (SIZE (1 .. 32)),				--- общедоступное имя инициатора связи
  voip-service-type    INTEGER (0 .. 255),					--- способ подключения
  voip-calling-number  DataVoipNumber,						--- номер вызывающего абонента
  voip-called-number   DataVoipNumber,						--- номер вызываемого абонента
  voip-in-bytes-count  INTEGER (0 .. 18446744073709551615),			--- объем переданных данных (включает как соединения управления так и передачи данных), байт
  voip-out-bytes-count INTEGER (0 .. 18446744073709551615),			--- объем принятых данных (включает как соединения управления так и передачи данных), байт
  voip-fax             BOOLEAN,							--- была попытка передачи факсовой информации (Т.38)
  voip-term-cause      INTEGER (0 .. 16384),					--- причина завершения соединения

  inbound-bunch [0]    Bunch OPTIONAL,						--- входящий пучок
  outbound-bunch [1]   Bunch OPTIONAL,						--- исходящий пучок
  voip-gateways [2]    SEQUENCE OF IPAddress OPTIONAL,				--- идентификаторы медиашлюзов, обслуживших соединение

  voip-protocol [3] VoipProtocol OPTIONAL,

  supplement-service-id [4] INTEGER (0 .. 4294967295) OPTIONAL,			--- ДВО при соединении
  voip-abonent-id [5]  UTF8String (SIZE (0 .. 64)) OPTIONAL	       	       	--- идентификатор абонента
}


--- запись IPDR трансляции сетевых адресов
dataAddressTranslationRecord TAGGED ::= {
  OID { sorm-report-connection-address-translations }
  DATA SEQUENCE OF DataAddressTranslationRecordContent
}

DataAddressTranslationRecordContent ::= SEQUENCE {
  telco-id         TelcoID,					--- идентификатор оператора связи или филиала
  point-id         INTEGER (0 .. 1000),				--- идентификатор точки подключения к сети передачи данных, с которой получена запись о соединении
  translation-time DateAndTime,					--- дата и время трансляции
  record-type ENUMERATED {					--- тип записи о трансляции сетевого адреса
      session-start (0),					--- начало сессии трансляции
      session-end (1)						--- окончание сессии трансляции
  },

  private-ip      NetworkPeerInfo,				--- внутренний адрес
  public-ip	  NetworkPeerInfo,				--- внешний адрес
  destination-ip  NetworkPeerInfo,				--- адрес назначения
  translation-type ENUMERATED {					--- тип трансляции сетевых адресов
	static-nat (0),						--- статическая
	dynamic-nat (1),					--- динамическая
	source-nat (2),						--- источника
	destination-nat (3),					--- получателя
	pat (4)							--- адрес-порт
  }
}


--- Data network header
DataNetworkCdrHeader ::= SEQUENCE {
   id TAGGED.&id ({DataNetworkHeaderVariants}),
   data TAGGED.&Data ({DataNetworkHeaderVariants}{@id})
}

DataNetworkHeaderVariants TAGGED ::= { dataNetworkCdrHeader }

dataNetworkCdrHeader TAGGED ::= {
  OID { sorm-report-connection-ipdr-header }
  DATA DataNetworkCdrHeaderData
}

DataNetworkCdrHeaderData ::= SEQUENCE {
  telco-id              TelcoID,						--- идентификатор оператора связи или филиала
  begin-connection-time DateAndTime,						--- дата и время начала соединения
  end-connection-time   DateAndTime,						--- дата и время завершения соединения
  client-info           NetworkPeerInfo,					--- информация о клиенте (IP/порт)
  server-info           NetworkPeerInfo,					--- информация о сервере (IP/порт)
  protocol-code         INTEGER (0 .. 65535),					--- код протокола в соответствии с RFC1700 либо номер порта для TCP/UDP
  point-id              INTEGER (0 .. 1000) OPTIONAL				--- идентификатор точки подключения к сети передачи данных, с которой получена запись о соединении
}

--- информация о входе в ресурс
IP-AAAInformation ::= SEQUENCE {
  username   UTF8String (SIZE (0..64)),   					--- пользоватеьлский логин
  aaaResult  IP-AAAResult OPTIONAL						--- результат операции входа
}

--- результат операции входа в ресурс
IP-AAAResult ::= ENUMERATED {
  aaaUnknown(1),								--- результат неизвестен
  aaaFailed(2),									--- неудачная попытка входа
  aaaSucceeded(3)								--- успешный вход
}


END
